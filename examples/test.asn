TICKET_ATTESTATION DEFINITIONS ::= BEGIN
  Attestation ::=  SEQUENCE  {
       signedInfo           SignedInfo,
       signatureAlgorithm   AlgorithmIdentifier,
       signatureValue       BIT STRING  }

  SignedInfo  ::=  SEQUENCE  {
       version         [0]  EXPLICIT Version,
       serialNumber         CertificateSerialNumber,
       signature            AlgorithmIdentifier,
       subjectPublicKeyInfo SubjectPublicKeyInfo,
       dataObject           TicketDataObject
  }

  TicketDataObject ::= SEQUENCE {
         match       INTEGER (1..51),
         class       ENUMERATED { club(0), lounge(1), silver(2), gold(3) },
         admission   INTEGER
  }

  Version  ::=  INTEGER  {  v1(0), v2(1), v3(2)  }

  CertificateSerialNumber  ::=  INTEGER

  Validity ::= SEQUENCE {
    notBefore      Time,
    notAfter       Time }

  Time ::= CHOICE {
        utcTime        UTCTime,
        generalTime    GeneralizedTime }

  SubjectPublicKeyInfo  ::=  SEQUENCE  {
        algorithm            AlgorithmIdentifier,
        subjectPublicKey     BIT STRING  }

  AlgorithmIdentifier  ::=  SEQUENCE OF OBJECT IDENTIFIER


   Name ::= CHOICE { -- only one possibility for now --
     rdnSequence  RDNSequence }

   RDNSequence ::= SEQUENCE OF RelativeDistinguishedName

   RelativeDistinguishedName ::=
     SET SIZE (1..MAX) OF AttributeTypeAndValue

   AttributeTypeAndValue ::= SEQUENCE {
     type     AttributeType,
     value    AttributeValue }

   AttributeType ::= OBJECT IDENTIFIER

   AttributeValue ::= ANY -- DEFINED BY AttributeType

   DirectoryString ::= CHOICE {
         teletexString           TeletexString (SIZE (1..MAX)),
         printableString         PrintableString (SIZE (1..MAX)),
         universalString         UniversalString (SIZE (1..MAX)),
         utf8String              UTF8String (SIZE (1..MAX)),
         bmpString               BMPString (SIZE (1..MAX)) }

END
