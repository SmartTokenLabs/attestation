AnonymouseIdentity

DEFINITIONS ::=
BEGIN

AnonymousIdentity ::= SEQUENCE {
    identifier       OCTET STRING,
    salt             OCTET STRING,
    type             IdentifierType
}
		

ReferenceIdentity ::= SEQUENCE {
    identity       PrintableString,
    salt           OCTET STRING,
    type           IdentifierType,
    proof          Schnorr 
}
		
IdentifierType ::= INTEGER { email(0), phone(0)}

Schnorr ::= SEQUENCE {
    generator       OCTET STRING,
    v               OCTET STRING,
    challenge       OCTET STRING,
    response        OCTET STRING 
}
		

END
