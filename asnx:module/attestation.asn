AttestationFramework

DEFINITIONS ::=
BEGIN

IMPORTS
    AlgorithmIdentifier,
    Version,
    CertificateSerialNumber,
    Validity,
    Extensions
        FROM AuthenticationFramework
    Name
        FROM InformationFramework;

MyAttestation ::=  SEQUENCE  {

     signedInfo           SignedInfo,
     signatureAlgorithm   AlgorithmIdentifier,
     signatureValue       BIT STRING  }

   SignedInfo ::=  SEQUENCE  {
     version         [0]  EXPLICIT Version,
     serialNumber         CertificateSerialNumber,
     signature            AlgorithmIdentifier,
     issuer               Name,
     validity             Validity,
     subject              Name,
     subjectPublicKeyInfo SubjectPublicKeyInfo,
     contract             SEQUENCE OF SmartContract OPTIONAL,
     attestsTo         CHOICE {
        extensions        [3] EXPLICIT Extensions,
        dataObject        [4] DataObject
     }
   }

   SubjectPublicKeyInfo ::= CHOICE {
     value       SubjectPublicKeyInfoValue,
     null        NULL 
   }
        
   SubjectPublicKeyInfoValue ::= SEQUENCE {
     algorithm              AlgorithmIdentifier,
     subjectPublicKey       BIT STRING 
   }

   SmartContract ::= INTEGER

   DataObject ::= INTEGER -- TODO Placeholder

END

AuthenticationFramework

DEFINITIONS ::=
BEGIN

AlgorithmIdentifier ::= SEQUENCE  {
    algorithm           OBJECT IDENTIFIER,
    parameters          ANY DEFINED BY algorithm OPTIONAL -- Some validators have a issue with this line
}

Version ::= INTEGER { v1(0), v2(1), v3(2) }

CertificateSerialNumber ::= INTEGER

Validity ::= CHOICE {
    value       ValidityValue,
    null        NULL 
}

ValidityValue ::= SEQUENCE {
    notBefore       Time,
    notAfter        Time 
}

Time ::= CHOICE {
	utcTime			UTCTime,	-- 1950 to 2049
	generalizedTime	GeneralizedTime
}

Extensions ::= SEQUENCE OF Extension

Extension ::= SEQUENCE {
	extnId		EXTENSION.&id,
	critical	BOOLEAN DEFAULT FALSE,
	extnValue	OCTET STRING
		-- contains a DER encoding of a value of type &ExtnType
		-- for the extension object identified by extnId
}

EXTENSION ::= CLASS {
	&id			OBJECT IDENTIFIER UNIQUE,
	&critical	BOOLEAN DEFAULT FALSE,
	-- critical is absent from the fourth edition X.509 ASN.1 module
	-- definitions.
	&ExtnType
}
WITH SYNTAX {
	SYNTAX			&ExtnType
	[ CRITICAL		&critical ]
	IDENTIFIED BY	&id
}

END

InformationFramework

DEFINITIONS ::=
BEGIN

Name ::= CHOICE {
	rdnSequence	RDNSequence, -- one possibility for now --
	null        NULL
}

RDNSequence ::= SEQUENCE OF RelativeDistinguishedName

   RelativeDistinguishedName ::=
     SET SIZE (1..MAX) OF AttributeTypeAndValue

   AttributeTypeAndValue ::= SEQUENCE {
     type     AttributeType,
     value    AttributeValue }

   AttributeType ::= OBJECT IDENTIFIER

   AttributeValue ::= ANY -- DEFINED BY AttributeType

END
