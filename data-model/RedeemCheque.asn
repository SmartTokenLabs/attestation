RedeemCheque

DEFINITIONS ::=
BEGIN

IMPORTS
    MyAttestation
        FROM AttestationFramework
    SignedCheque
        FROM SignedCheque;

RedeemCheque ::= SEQUENCE {
    signedCheque         SignedCheque,
    attestation          MyAttestation,
    proof                Proof,
    signatureValue       BIT STRING 
}
		

Proof ::= SEQUENCE {
    base                 OCTET STRING,
    riddle               OCTET STRING,
    challengePoint       OCTET STRING,
    responseValue         OCTET STRING
}
		

END
