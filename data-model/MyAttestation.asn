MyAttestation

DEFINITIONS ::=
BEGIN
Attestation { DataObject } ::=  SEQUENCE  {

     signedInfo           SignedInfo { DataObject },
     signatureAlgorithm   AlgorithmIdentifier,
     signatureValue       BIT STRING  }

   SignedInfo {  DataObject }  ::=  SEQUENCE  {
     version         [0]  EXPLICIT Version,
     serialNumber         CertificateSerialNumber,
     signature            AlgorithmIdentifier,
     issuer               Name OPTIONAL,
     validity             Validity OPTIONAL,
     subject              Name OPTIONAL,
     subjectPublicKeyInfo SubjectPublicKeyInfo OPTIONAL,
     contract             SEQUENCE OF SmartContract OPTIONAL,
     attestsTo            CHOICE {
         dataObject  [0]      DataObject, -- defined per objectClass
         extensions  [3]      EXPLICIT Extensions
     }
   }

END
