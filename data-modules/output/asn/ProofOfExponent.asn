ProofOfExponent

DEFINITIONS ::=
BEGIN

Proof ::= SEQUENCE {
    riddle               OCTET STRING,
    challengePoint       OCTET STRING,
    responseValue        OCTET STRING,
    unpredictableNumber  OCTET STRING
}

-- Proof data needed when the riddle can be determined from other data objects --
UsageProof ::= SEQUENCE {
    challengePoint       OCTET STRING,
    responseValue        OCTET STRING,
    unpredictableNumber  OCTET STRING
}

END
