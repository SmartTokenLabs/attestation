SignedDevconTicket

DEFINITIONS ::=
BEGIN

IMPORTS
AlgorithmIdentifier FROM AuthenticationFramework;

SignedDevconTicket ::= SEQUENCE {
    ticket               DevconTicket,
    signatureAlgorithm   AlgorithmIdentifier,
    signatureValue       BIT STRING
}


DevconTicket ::= SEQUENCE {
    devonId     INTEGER,
    ticketId         INTEGER,
    ticketClass      INTEGER,
--  (currently not specified)      --
--  co2_token         OCTET STRING --
    riddle         OCTET STRING
}

END
