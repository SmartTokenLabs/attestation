AttestationRequest

DEFINITIONS ::=
BEGIN

IMPORTS
    Proof
        FROM ProofOfExponent;

Identity ::= SEQUENCE {
    type               IdentifierType,
    proof              Proof
}
		
IdentifierType ::= INTEGER { email(0), phone(1)}

END
