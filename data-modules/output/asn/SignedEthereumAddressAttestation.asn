SignedEthereumAddressLinkingAttestation

DEFINITIONS ::=
BEGIN

IMPORTS
    Address
        FROM NFTAttestation
    AlgorithmIdentifier,
    SubjectPublicKeyInfoValue
        FROM AuthenticationFramework;

Validity ::= SEQUENCE {
    notBefore                     INTEGER, -- NotBefore time since epoch in seconds
    notAfter                      INTEGER  -- NotAfter time since epoch in seconds
}

EthereumAddressLinkingAttestation ::= SEQUENCE {
    subtlePublicKey               SubjectPublicKeyInfoValue,
    subjectAddress                Address,
    validity                      Validity,
    context                       OCTET STRING OPTIONAL
}

SignedEthereumAddressLinkingAttestation ::= SEQUENCE {
    ethereumAddressAttestation    EthereumAddressLinkingAttestation,
    signingAlgorithm              AlgorithmIdentifier,
    signatureValue                BIT STRING
}

END
