SignedDevconTicket

DEFINITIONS ::=
BEGIN

IMPORTS
AlgorithmIdentifier FROM AuthenticationFramework;

SignedDevconTicket ::= SEQUENCE {
    ticket           DevconTicket,
    signatureValue   BIT STRING
}


DevconTicket ::= SEQUENCE {
    devconId         UTF8String,
    ticketId         TicketId,
    ticketClass      INTEGER,
--  (currently not specified)      --
--  co2_token         OCTET STRING --
    commitment       OCTET STRING
}

TicketId ::= CHOICE {
  integerId        INTEGER,
  stringId         UTF8String
}

END
