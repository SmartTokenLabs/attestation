SignedNFTAttestation

DEFINITIONS ::=
BEGIN

IMPORTS
    NFTAttestation
        FROM NFTAttestation
    AlgorithmIdentifier
        FROM AuthenticationFramework;

-- Version 1 or 2, newer uses EIP712 --
SignedNFTAttestation ::= SEQUENCE {
    nftAttestation       NFTAttestation,
    signingVersion       INTEGER OPTIONAL,
    signingAlgorithm     AlgorithmIdentifier,
    signatureValue       BIT STRING
}

END
