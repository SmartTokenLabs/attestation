TransObject

DEFINITIONS ::=
BEGIN

IMPORTS
    NFTAttestation
        FROM NFTAttestation;

TransObject ::= SEQUENCE {
    tokens               Tokens,
    attestation          NFTAttestation,
    signatureValue       BIT STRING
}

Tokens ::= SEQUENCE SIZE (1..MAX) OF ERC721

-- See https://eips.ethereum.org/EIPS/eip-721 for details --
ERC721 ::= SEQUENCE {
    tokenId       TokenId,
    address       Address
}

-- The 256 bit non-negative integer uniquely representing the ERC721 token in question in binary --
TokenId ::= OCTET STRING (SIZE(32))

-- The binary encoding of the 20 bytes representing an Ethereum address --
Address ::= OCTET STRING (SIZE(20))

END
