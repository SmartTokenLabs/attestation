NFTAttestation

DEFINITIONS ::=
BEGIN

IMPORTS
    UriIdAttestation
        FROM UriIdAttestation;

NFTAttestation ::= SEQUENCE {
    creator              UriIdAttestation,
    -- At least one token OR "nftDigest" MUST be included --
    tokens               Tokens,
    -- Digest of the content (pic/vid) of the NFT --
    nftDigest            Digest OPTIONAL
}

-- Allowed to be empty if "nftDigest" is included --
Tokens ::= SEQUENCE OF ERC721

-- A hash digest --
Digest ::= OCTET STRING (SIZE(32..MAX))

-- See https://eips.ethereum.org/EIPS/eip-721 for details --
ERC721 ::= SEQUENCE {
    address       Address,
    chainId       INTEGER,
    tokenIds      SEQUENCE OF TokenId OPTIONAL
}

-- The 256 bit non-negative integer uniquely representing the ERC721 token in question in binary --
TokenId ::= OCTET STRING (SIZE(32))

-- The binary encoding of the 20 bytes representing an Ethereum address --
Address ::= OCTET STRING (SIZE(20))

END
