UseDevconTicket

DEFINITIONS ::=
BEGIN

IMPORTS
    MyAttestation
        FROM AttestationFramework
    SignedDevconTicket
        FROM SignedDevconTicket
    UsageProof
        FROM ProofOfExponent;

UseDevconTicket ::= SEQUENCE {
    signedDevconTicket         SignedDevconTicket,
    attestation          MyAttestation,
    proof                UsageProof
}

END
