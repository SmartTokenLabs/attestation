AuthenticationFramework

DEFINITIONS ::=
BEGIN

AlgorithmIdentifier ::= SEQUENCE  {
    algorithm           OBJECT IDENTIFIER,
    parameters          ANY DEFINED BY algorithm OPTIONAL -- Some validators have a issue with this line
}

Version ::= INTEGER { v1(0), v2(1), v3(2) }

CertificateSerialNumber ::= INTEGER

Validity ::= CHOICE {
    value       ValidityValue,
    null        NULL 
}
		
ValidityValue ::= SEQUENCE {
    notBefore       GeneralizedTime,
    notBeforeInt    INTEGER OPTIONAL, -- NotBefore time since epoch in seconds
    notAfter        GeneralizedTime,
    notAfterInt     INTEGER OPTIONAL -- NotAfter time since epoch in seconds
}

Extensions ::= SEQUENCE OF Extension

Extension ::= SEQUENCE {
	extnId		EXTENSION.&id,
	critical	BOOLEAN DEFAULT FALSE,
	extnValue	OCTET STRING
		-- contains a DER encoding of a value of type &ExtnType
		-- for the extension object identified by extnId
}

EXTENSION ::= CLASS {
	&id			OBJECT IDENTIFIER UNIQUE,
	&critical	BOOLEAN DEFAULT FALSE,
	-- critical is absent from the fourth edition X.509 ASN.1 module
	-- definitions.
	&ExtnType
}
WITH SYNTAX {
	SYNTAX			&ExtnType
	[ CRITICAL		&critical ]
	IDENTIFIED BY	&id
}

END
