NFTOffer

DEFINITIONS ::=
BEGIN

IMPORTS
    NFTAttestation
        FROM NFTAttestation
    ValidityValue
        FROM AuthenticationFramework;

NFTOffer ::= SEQUENCE {
    nftAttestation      NFTAttestation,
    -- Price in Gwei --
    price               INTEGER,
    validity            ValidityValue
}

END
