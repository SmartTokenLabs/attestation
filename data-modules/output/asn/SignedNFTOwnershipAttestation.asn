SignedNFTOwnershipAttestation

DEFINITIONS ::=
BEGIN

IMPORTS
    Tokens
        FROM NFTAttestation
    AlgorithmIdentifier,
    SubjectPublicKeyInfoValue
        FROM AuthenticationFramework;

Validity ::= SEQUENCE {
    notBefore                     INTEGER, -- NotBefore time since epoch in seconds
    notAfter                      INTEGER  -- NotAfter time since epoch in seconds
}

NFTOwnershipAttestation ::= SEQUENCE {
    subtlePublicKey               SubjectPublicKeyInfoValue,
    tokens                        Tokens,
    validity                      Validity,
    context                       OCTET STRING OPTIONAL
}

SignedNFTOwnershipAttestation ::= SEQUENCE {
    nftOwnershipAttestation       NFTOwnershipAttestation,
    signingAlgorithm              AlgorithmIdentifier,
    signatureValue                BIT STRING
}

END
